# 14 CFR Part 25 - Transport Category Airplane Certification
FAA 14 CFR Part 25 - Transport Category Airplanes Certification Requirements Overview

# Specification: 14 CFR Part 25 - Derived Shall Requirements

## SUBPART_A: Subpart A - General (25.1 - 25.5) (Subpart)

### CERT-GEN-001 (Requirement)
Applicability: This part prescribes airworthiness standards for the issuance of type certificates, and changes to those certificates, for transport category airplanes. Applies to: (1) Jets with 10+ seats or MTOW > 12,500 lbs; (2) Propeller aircraft with 19+ seats or MTOW > 19,000 lbs.
- CFR Reference: 25.1
- Source: 14 CFR Part 25
- Criticality: Regulatory
- Verification Method: Analysis
- Compliance Status: Not Started

#### CERT-GEN-001-DS-1 (Requirement)
§25.1(a): This part prescribes airworthiness standards for the issue of type certificates, and changes to those certificates, for transport category airplanes.
- CFR Reference: 25.1
- Source: Derived from 14 CFR Part 25
- Criticality: Regulatory
- Verification Method: Analysis
- Compliance Status: Not Started

#### CERT-GEN-001-DS-2 (Requirement)
§25.1(b): Each person who applies under Part 21 for such a certificate or change must show compliance with the applicable requirements in this part.
- CFR Reference: 25.1
- Source: Derived from 14 CFR Part 25
- Criticality: Regulatory
- Verification Method: Analysis
- Compliance Status: Not Started

#### CERT-GEN-001-DS-3 (Requirement)
§25.1: Transport category applies to jets with 10+ seats or MTOW >12,500 lbs, or propeller aircraft with 19+ seats or MTOW >19,000 lbs.
- CFR Reference: 25.1
- Source: Derived from 14 CFR Part 25
- Criticality: Regulatory
- Verification Method: Analysis
- Compliance Status: Not Started

## SUBPART_B: Subpart B - Flight (25.21 - 25.255) (Subpart)

### CERT-FLT-001 (Requirement)
Proof of Compliance: Compliance with the flight requirements must be shown by tests upon an airplane of the type for which certification is requested, or by calculations based on test data from similar airplane configurations.
- CFR Reference: 25.21
- Source: 14 CFR Part 25
- Criticality: Regulatory
- Verification Method: Analysis
- Compliance Status: Not Started

#### CERT-FLT-001-DS-1 (Requirement)
§25.21(a): Each requirement must be met at each appropriate combination of weight and center of gravity within the range of loading conditions.
- CFR Reference: 25.21
- Source: Derived from 14 CFR Part 25
- Criticality: Regulatory
- Verification Method: Test
- Compliance Status: Not Started

#### CERT-FLT-001-DS-2 (Requirement)
§25.21(a): Compliance must be shown by tests upon an airplane of the type for which certification is requested, or by calculations based on, and equal in accuracy to, the results of testing.
- CFR Reference: 25.21
- Source: Derived from 14 CFR Part 25
- Criticality: Regulatory
- Verification Method: Test
- Compliance Status: Not Started

#### CERT-FLT-001-DS-3 (Requirement)
§25.21(c): Controllability, stability, trim, and stalling characteristics must be shown for each altitude up to the maximum expected in operation.
- CFR Reference: 25.21
- Source: Derived from 14 CFR Part 25
- Criticality: Regulatory
- Verification Method: Test
- Compliance Status: Not Started

### CERT-FLT-002 (Requirement)
Takeoff Performance: The airplane must meet takeoff performance requirements including: accelerate-stop distance, takeoff distance, takeoff run, and one-engine-inoperative takeoff flight path. Must account for runway slope, wind, and atmospheric conditions.
- CFR Reference: 25.101-25.125
- Source: 14 CFR Part 25
- Criticality: Safety-Critical
- Verification Method: Analysis
- Compliance Status: Not Started

#### CERT-FLT-002-DS-1 (Requirement)
§25.101(a): Unless otherwise prescribed, airplanes must meet the applicable performance requirements of this subpart for ambient atmospheric conditions and still air.
- CFR Reference: 25.101-25.125
- Source: Derived from 14 CFR Part 25
- Criticality: Safety-Critical
- Verification Method: Test
- Compliance Status: Not Started

#### CERT-FLT-002-DS-2 (Requirement)
§25.101(c): Performance must account for the propulsive thrust available under the particular ambient atmospheric conditions, including installation losses and accessory power absorption.
- CFR Reference: 25.101-25.125
- Source: Derived from 14 CFR Part 25
- Criticality: Safety-Critical
- Verification Method: Test
- Compliance Status: Not Started

#### CERT-FLT-002-DS-3 (Requirement)
§25.101(i): Accelerate-stop and landing distances must be determined with all airplane wheel brake assemblies at the fully worn limit of their allowable wear range.
- CFR Reference: 25.101-25.125
- Source: Derived from 14 CFR Part 25
- Criticality: Safety-Critical
- Verification Method: Test
- Compliance Status: Not Started

### CERT-FLT-003 (Requirement)
Landing Performance: Landing distance must be determined on a level, smooth, dry, hard-surfaced runway. Must demonstrate performance with and without thrust reversers, at maximum landing weight.
- CFR Reference: 25.119-25.125
- Source: 14 CFR Part 25
- Criticality: Safety-Critical
- Verification Method: Analysis
- Compliance Status: Not Started

#### CERT-FLT-003-DS-1 (Requirement)
§25.119: In the landing configuration, the steady gradient of climb may not be less than 3.2% for two-engine airplanes with critical engine inoperative.
- CFR Reference: 25.119-25.125
- Source: Derived from 14 CFR Part 25
- Criticality: Safety-Critical
- Verification Method: Test
- Compliance Status: Not Started

#### CERT-FLT-003-DS-2 (Requirement)
§25.125(a): The horizontal distance necessary to land and come to a complete stop from a point 50 feet above the landing surface must be determined.
- CFR Reference: 25.119-25.125
- Source: Derived from 14 CFR Part 25
- Criticality: Safety-Critical
- Verification Method: Test
- Compliance Status: Not Started

#### CERT-FLT-003-DS-3 (Requirement)
§25.125(b): Landing distances must be determined on a level, smooth, dry, hard-surfaced runway using operational procedures.
- CFR Reference: 25.119-25.125
- Source: Derived from 14 CFR Part 25
- Criticality: Safety-Critical
- Verification Method: Test
- Compliance Status: Not Started

### CERT-FLT-004 (Requirement)
Stall Speed (V_S): Reference stall speed V_SR must be determined in 1-g flight using a method that produces minimum speed with wings level. V_S1 and V_SR must be established for each configuration.
- CFR Reference: 25.103
- Source: 14 CFR Part 25
- Criticality: Safety-Critical
- Verification Method: Analysis
- Compliance Status: Not Started

#### CERT-FLT-004-DS-1 (Requirement)
§25.103(a): The reference stall speed VSR is a calibrated airspeed defined by the applicant as an equivalent airspeed with respect to the 1-g stall speed.
- CFR Reference: 25.103
- Source: Derived from 14 CFR Part 25
- Criticality: Safety-Critical
- Verification Method: Test
- Compliance Status: Not Started

#### CERT-FLT-004-DS-2 (Requirement)
§25.103(b): VSR must be determined with zero thrust at the stall speed, or with thrust not exceeding that required for level flight at 1.5VSR.
- CFR Reference: 25.103
- Source: Derived from 14 CFR Part 25
- Criticality: Safety-Critical
- Verification Method: Test
- Compliance Status: Not Started

#### CERT-FLT-004-DS-3 (Requirement)
§25.103(c): The stall warning must begin at a speed exceeding the stall speed by a sufficient margin to allow the pilot to prevent stalling.
- CFR Reference: 25.103
- Source: Derived from 14 CFR Part 25
- Criticality: Safety-Critical
- Verification Method: Test
- Compliance Status: Not Started

## SUBPART_C: Subpart C - Structure (25.301 - 25.581) (Subpart)

### CERT-STR-001 (Requirement)
Loads General: Strength requirements are specified in terms of limit loads (maximum loads expected in service) and ultimate loads (limit loads multiplied by prescribed factors of safety, typically 1.5). Structure must withstand limit loads without detrimental permanent deformation.
- CFR Reference: 25.301-25.307
- Source: 14 CFR Part 25
- Criticality: Safety-Critical
- Verification Method: Analysis
- Compliance Status: Not Started

#### CERT-STR-001-DS-1 (Requirement)
§25.301(a): Strength requirements are specified in terms of limit loads (maximum loads expected in service) and ultimate loads (limit loads multiplied by prescribed factors of safety).
- CFR Reference: 25.301-25.307
- Source: Derived from 14 CFR Part 25
- Criticality: Safety-Critical
- Verification Method: Analysis/Test
- Compliance Status: Not Started

#### CERT-STR-001-DS-2 (Requirement)
§25.301(b): Air, ground, and water loads must be placed in equilibrium with inertia forces, considering each item of mass in the airplane.
- CFR Reference: 25.301-25.307
- Source: Derived from 14 CFR Part 25
- Criticality: Safety-Critical
- Verification Method: Analysis/Test
- Compliance Status: Not Started

#### CERT-STR-001-DS-3 (Requirement)
§25.301(c): If deflections under load significantly change the distribution of external or internal loads, this redistribution must be taken into account.
- CFR Reference: 25.301-25.307
- Source: Derived from 14 CFR Part 25
- Criticality: Safety-Critical
- Verification Method: Analysis/Test
- Compliance Status: Not Started

### CERT-STR-002 (Requirement)
Flight Maneuver Envelope: The structure must be designed for symmetric maneuver conditions within the V-n diagram. Positive limit maneuvering load factor of at least 2.5 at V_C and negative load factor capability as specified. Gust loads per continuous turbulence and discrete gust requirements.
- CFR Reference: 25.331-25.341
- Source: 14 CFR Part 25
- Criticality: Safety-Critical
- Verification Method: Analysis
- Compliance Status: Not Started

#### CERT-STR-002-DS-1 (Requirement)
§25.303: Unless otherwise specified, a factor of safety of 1.5 must be applied to the prescribed limit load which are considered external loads on the structure.
- CFR Reference: 25.331-25.341
- Source: Derived from 14 CFR Part 25
- Criticality: Safety-Critical
- Verification Method: Analysis/Test
- Compliance Status: Not Started

#### CERT-STR-002-DS-2 (Requirement)
§25.305(a): The structure must be able to support limit loads without detrimental permanent deformation.
- CFR Reference: 25.331-25.341
- Source: Derived from 14 CFR Part 25
- Criticality: Safety-Critical
- Verification Method: Analysis/Test
- Compliance Status: Not Started

#### CERT-STR-002-DS-3 (Requirement)
§25.305(b): The structure must be able to support ultimate loads without failure for at least 3 seconds.
- CFR Reference: 25.331-25.341
- Source: Derived from 14 CFR Part 25
- Criticality: Safety-Critical
- Verification Method: Analysis/Test
- Compliance Status: Not Started

### CERT-STR-003 (Requirement)
Emergency Landing Conditions: The structure must protect occupants under emergency landing conditions. Static loads: 9g forward, 1.5g aft, 3g upward, 6g downward, 3g sideward. Dynamic test conditions for seats and restraint systems.
- CFR Reference: 25.561-25.562
- Source: 14 CFR Part 25
- Criticality: Safety-Critical
- Verification Method: Analysis
- Compliance Status: Not Started

#### CERT-STR-003-DS-1 (Requirement)
§25.571(a): An evaluation must be conducted to show that catastrophic failure due to fatigue, corrosion, manufacturing defects, or accidental damage will be avoided throughout the operational life.
- CFR Reference: 25.561-25.562
- Source: Derived from 14 CFR Part 25
- Criticality: Safety-Critical
- Verification Method: Analysis/Test
- Compliance Status: Not Started

#### CERT-STR-003-DS-2 (Requirement)
§25.571(b): Damage-tolerance evaluation must include a determination of probable locations and modes of damage, and inspection thresholds and intervals.
- CFR Reference: 25.561-25.562
- Source: Derived from 14 CFR Part 25
- Criticality: Safety-Critical
- Verification Method: Analysis/Test
- Compliance Status: Not Started

#### CERT-STR-003-DS-3 (Requirement)
§25.571(b): A limit of validity (LOV) of the engineering data that supports the structural maintenance program must be established.
- CFR Reference: 25.561-25.562
- Source: Derived from 14 CFR Part 25
- Criticality: Safety-Critical
- Verification Method: Analysis/Test
- Compliance Status: Not Started

### CERT-STR-004 (Requirement)
Damage Tolerance Evaluation: An evaluation of the structure must show that catastrophic failure due to fatigue, corrosion, manufacturing defects, or accidental damage will be avoided throughout operational life. Requires inspection programs and retirement times for Principal Structural Elements (PSEs).
- CFR Reference: 25.571
- Source: 14 CFR Part 25
- Criticality: Safety-Critical
- Verification Method: Analysis
- Compliance Status: Not Started

#### CERT-STR-004-DS-1 (Requirement)
§25.581(a): The airplane must be protected against catastrophic effects from lightning.
- CFR Reference: 25.571
- Source: Derived from 14 CFR Part 25
- Criticality: Safety-Critical
- Verification Method: Analysis/Test
- Compliance Status: Not Started

#### CERT-STR-004-DS-2 (Requirement)
§25.581(b): For metallic components, acceptable methods of protection include bonding and grounding to disperse lightning currents.
- CFR Reference: 25.571
- Source: Derived from 14 CFR Part 25
- Criticality: Safety-Critical
- Verification Method: Analysis/Test
- Compliance Status: Not Started

#### CERT-STR-004-DS-3 (Requirement)
§25.581(c): For non-metallic components, acceptable methods include installation of conductive materials to provide lightning current paths.
- CFR Reference: 25.571
- Source: Derived from 14 CFR Part 25
- Criticality: Safety-Critical
- Verification Method: Analysis/Test
- Compliance Status: Not Started

## SUBPART_D: Subpart D - Design and Construction (25.601 - 25.899) (Subpart)

### CERT-DES-001 (Requirement)
Materials and Fabrication: Materials must have design values based on adequate test data and conform to approved specifications. Fabrication methods must produce consistently sound structures with repeatable properties.
- CFR Reference: 25.601-25.609
- Source: 14 CFR Part 25
- Criticality: Safety-Critical
- Verification Method: Analysis
- Compliance Status: Not Started

#### CERT-DES-001-DS-1 (Requirement)
§25.603(a): The suitability and durability of materials used for parts, the failure of which could adversely affect safety, must be established on the basis of experience or tests.
- CFR Reference: 25.601-25.609
- Source: Derived from 14 CFR Part 25
- Criticality: Safety-Critical
- Verification Method: Inspection
- Compliance Status: Not Started

#### CERT-DES-001-DS-2 (Requirement)
§25.603(b): Materials must conform to approved specifications that ensure their having the strength and other properties assumed in the design data.
- CFR Reference: 25.601-25.609
- Source: Derived from 14 CFR Part 25
- Criticality: Safety-Critical
- Verification Method: Inspection
- Compliance Status: Not Started

#### CERT-DES-001-DS-3 (Requirement)
§25.605: Fabrication methods must produce consistently sound structure. Special processes must be performed under approved process specifications.
- CFR Reference: 25.601-25.609
- Source: Derived from 14 CFR Part 25
- Criticality: Safety-Critical
- Verification Method: Inspection
- Compliance Status: Not Started

### CERT-DES-002 (Requirement)
Control Systems: Flight control systems must operate easily, smoothly, and positively. Must be designed to minimize jamming, chafing, and interference. Redundancy and failure modes analysis required for fly-by-wire systems.
- CFR Reference: 25.671-25.703
- Source: 14 CFR Part 25
- Criticality: Safety-Critical
- Verification Method: Analysis
- Compliance Status: Not Started

#### CERT-DES-002-DS-1 (Requirement)
§25.671(a): Each control system must operate with the ease, smoothness, and positiveness appropriate to its function.
- CFR Reference: 25.671-25.703
- Source: Derived from 14 CFR Part 25
- Criticality: Safety-Critical
- Verification Method: Inspection
- Compliance Status: Not Started

#### CERT-DES-002-DS-2 (Requirement)
§25.671(c): The airplane must be shown by analysis, test, or both, to be capable of continued safe flight and landing after any single failure in the flight control system.
- CFR Reference: 25.671-25.703
- Source: Derived from 14 CFR Part 25
- Criticality: Safety-Critical
- Verification Method: Inspection
- Compliance Status: Not Started

#### CERT-DES-002-DS-3 (Requirement)
§25.671(d): All failures not shown to be extremely improbable must be considered, including jamming, disconnection, unintended engagement, or runaway.
- CFR Reference: 25.671-25.703
- Source: Derived from 14 CFR Part 25
- Criticality: Safety-Critical
- Verification Method: Inspection
- Compliance Status: Not Started

### CERT-DES-003 (Requirement)
Landing Gear: Landing gear must be designed for all loading conditions including ground loads, tire failures, and retraction/extension cycles. Position indicating systems, braking systems, and steering systems requirements.
- CFR Reference: 25.721-25.737
- Source: 14 CFR Part 25
- Criticality: Safety-Critical
- Verification Method: Analysis
- Compliance Status: Not Started

#### CERT-DES-003-DS-1 (Requirement)
§25.721: The landing gear system must be designed so that when it fails due to overloads during takeoff and landing, the failure mode is not likely to cause spillage of enough fuel to constitute a fire hazard.
- CFR Reference: 25.721-25.737
- Source: Derived from 14 CFR Part 25
- Criticality: Safety-Critical
- Verification Method: Inspection
- Compliance Status: Not Started

#### CERT-DES-003-DS-2 (Requirement)
§25.729(a): The landing gear retracting mechanism must be designed so that the landing gear can be extended in case of failure of the normal landing gear operating mechanism.
- CFR Reference: 25.721-25.737
- Source: Derived from 14 CFR Part 25
- Criticality: Safety-Critical
- Verification Method: Inspection
- Compliance Status: Not Started

#### CERT-DES-003-DS-3 (Requirement)
§25.735: Brakes must be designed to prevent hazardous accumulation of heat; the brake temperature must be within operating limits after rejected takeoff at maximum energy.
- CFR Reference: 25.721-25.737
- Source: Derived from 14 CFR Part 25
- Criticality: Safety-Critical
- Verification Method: Inspection
- Compliance Status: Not Started

### CERT-DES-004 (Requirement)
Doors and Emergency Exits: Passenger and crew doors must have positive locking mechanisms. Emergency exits must be openable from inside and outside, with clear marking. Minimum exit dimensions and distribution requirements for rapid evacuation.
- CFR Reference: 25.783-25.789
- Source: 14 CFR Part 25
- Criticality: Safety-Critical
- Verification Method: Analysis
- Compliance Status: Not Started

#### CERT-DES-004-DS-1 (Requirement)
§25.801(a): If certification with ditching provisions is requested, the airplane must meet the requirements of this section and §§25.807(e), 25.1411, and 25.1415(a).
- CFR Reference: 25.783-25.789
- Source: Derived from 14 CFR Part 25
- Criticality: Safety-Critical
- Verification Method: Inspection
- Compliance Status: Not Started

#### CERT-DES-004-DS-2 (Requirement)
§25.801(b): Each practicable design measure must be taken to minimize the probability that in an emergency landing on water, the behavior of the airplane would cause immediate injury to the occupants.
- CFR Reference: 25.783-25.789
- Source: Derived from 14 CFR Part 25
- Criticality: Safety-Critical
- Verification Method: Inspection
- Compliance Status: Not Started

#### CERT-DES-004-DS-3 (Requirement)
§25.807: Emergency exits must be distributed as uniformly as practical, and the number and types must meet the requirements for maximum seating capacity.
- CFR Reference: 25.783-25.789
- Source: Derived from 14 CFR Part 25
- Criticality: Safety-Critical
- Verification Method: Inspection
- Compliance Status: Not Started

## SUBPART_E: Subpart E - Powerplant (25.901 - 25.1207) (Subpart)

### General
General - 14 CFR 25.901-25.945
- CFR Reference: 25.901-25.945
- Source: 14 CFR Part 25

#### CERT-PWR-0101 (Requirement)
§25.901 Installation: For the purpose of this part, the airplane powerplant installation includes each component that is necessary for propulsion, affects the control of the major propulsive units, or affects the safety of the major propulsive units between normal inspections or overhauls.
- CFR Reference: 25.901
- Source: 14 CFR Part 25
- Criticality: Safety-Critical
- Verification Method: Test
- Compliance Status: Not Started

##### CERT-PWR-0101-DS-1 (Requirement)
§25.901(a): The powerplant installation includes each component necessary for propulsion that affects control of major propulsive units or affects safety between normal inspections or overhauls.
- CFR Reference: 25.901
- Source: Derived from 14 CFR Part 25
- Criticality: Safety-Critical
- Verification Method: Test
- Compliance Status: Not Started

##### CERT-PWR-0101-DS-2 (Requirement)
§25.901(b): Each powerplant and auxiliary power unit installation must be constructed and arranged to ensure safe continued operation and accessibility for necessary inspections and maintenance.
- CFR Reference: 25.901
- Source: Derived from 14 CFR Part 25
- Criticality: Safety-Critical
- Verification Method: Test
- Compliance Status: Not Started

##### CERT-PWR-0101-DS-3 (Requirement)
§25.901(c): Powerplant and auxiliary power unit installations must comply with §25.1309 requirements for equipment, systems, and installations.
- CFR Reference: 25.901
- Source: Derived from 14 CFR Part 25
- Criticality: Safety-Critical
- Verification Method: Test
- Compliance Status: Not Started

#### CERT-PWR-0102 (Requirement)
§25.903 Engines: Each engine must have a type certificate and meet applicable requirements. The powerplants must be arranged and isolated from each other to allow operation so that failure or malfunction of any engine will not prevent continued safe operation of remaining engines.
- CFR Reference: 25.903
- Source: 14 CFR Part 25
- Criticality: Safety-Critical
- Verification Method: Test
- Compliance Status: Not Started

##### CERT-PWR-0102-DS-1 (Requirement)
§25.903(a): Each engine must have a type certificate and meet the applicable requirements of part 34 of this chapter.
- CFR Reference: 25.903
- Source: Derived from 14 CFR Part 25
- Criticality: Safety-Critical
- Verification Method: Test
- Compliance Status: Not Started

##### CERT-PWR-0102-DS-2 (Requirement)
§25.903(b): The powerplants must be arranged and isolated from each other to allow operation so that failure or malfunction of any engine will not prevent continued safe operation of remaining engines.
- CFR Reference: 25.903
- Source: Derived from 14 CFR Part 25
- Criticality: Safety-Critical
- Verification Method: Test
- Compliance Status: Not Started

##### CERT-PWR-0102-DS-3 (Requirement)
§25.903(d): For turbine engine installations, design precautions must be taken to minimize the hazards to the airplane in the event of an engine rotor failure or fire that burns through the engine case.
- CFR Reference: 25.903
- Source: Derived from 14 CFR Part 25
- Criticality: Safety-Critical
- Verification Method: Test
- Compliance Status: Not Started

##### CERT-PWR-0102-DS-4 (Requirement)
§25.903(e): Means must be provided for restarting any engine in flight. The altitude and airspeed envelope for engine restart must be established.
- CFR Reference: 25.903
- Source: Derived from 14 CFR Part 25
- Criticality: Safety-Critical
- Verification Method: Test
- Compliance Status: Not Started

#### CERT-PWR-0103 (Requirement)
§25.905 Propellers: Each propeller must have a type certificate. Engine power and propeller shaft rotational speed may not exceed the limits for which the propeller is certificated.
- CFR Reference: 25.905
- Source: 14 CFR Part 25
- Criticality: Safety-Critical
- Verification Method: Test
- Compliance Status: Not Started

##### CERT-PWR-0103-DS-1 (Requirement)
§25.905(a): Each propeller must have a type certificate.
- CFR Reference: 25.905
- Source: Derived from 14 CFR Part 25
- Criticality: Safety-Critical
- Verification Method: Test
- Compliance Status: Not Started

##### CERT-PWR-0103-DS-2 (Requirement)
§25.905(b): Engine power and propeller shaft rotational speed may not exceed the limits for which the propeller is certificated.
- CFR Reference: 25.905
- Source: Derived from 14 CFR Part 25
- Criticality: Safety-Critical
- Verification Method: Test
- Compliance Status: Not Started

##### CERT-PWR-0103-DS-3 (Requirement)
§25.905(d): Design precautions must be taken to minimize the hazards to the airplane in the event a propeller blade fails or is released by a hub failure.
- CFR Reference: 25.905
- Source: Derived from 14 CFR Part 25
- Criticality: Safety-Critical
- Verification Method: Test
- Compliance Status: Not Started

### Fuel System
Fuel System - 14 CFR 25.951-25.1001
- CFR Reference: 25.951-25.1001
- Source: 14 CFR Part 25

#### CERT-PWR-0201 (Requirement)
§25.951 Fuel System General: Each fuel system must be constructed and arranged to ensure a flow of fuel at a rate and pressure established for proper engine and auxiliary power unit functioning under each likely operating condition.
- CFR Reference: 25.951
- Source: 14 CFR Part 25
- Criticality: Safety-Critical
- Verification Method: Test
- Compliance Status: Not Started

##### CERT-PWR-0201-DS-1 (Requirement)
§25.951(a): Each fuel system must be constructed and arranged to ensure fuel flow at a rate and pressure established for proper engine functioning under each likely operating condition.
- CFR Reference: 25.951
- Source: Derived from 14 CFR Part 25
- Criticality: Safety-Critical
- Verification Method: Test
- Compliance Status: Not Started

##### CERT-PWR-0201-DS-2 (Requirement)
§25.951(b): Each fuel system must be arranged so that no air introduced into the system will result in flameout for turbine engines or power interruption for more than 20 seconds for reciprocating engines.
- CFR Reference: 25.951
- Source: Derived from 14 CFR Part 25
- Criticality: Safety-Critical
- Verification Method: Test
- Compliance Status: Not Started

##### CERT-PWR-0201-DS-3 (Requirement)
§25.951(c): Each turbine engine fuel system must be capable of sustained operation with fuel initially saturated with water at 80°F and cooled to the most critical icing condition.
- CFR Reference: 25.951
- Source: Derived from 14 CFR Part 25
- Criticality: Safety-Critical
- Verification Method: Test
- Compliance Status: Not Started

#### CERT-PWR-0202 (Requirement)
§25.963 Fuel Tanks: General: Each fuel tank must be able to withstand the applicable pressure tests without failure or leakage. Each fuel tank must have adequate structural strength to withstand applicable loads.
- CFR Reference: 25.963
- Source: 14 CFR Part 25
- Criticality: Safety-Critical
- Verification Method: Test
- Compliance Status: Not Started

##### CERT-PWR-0202-DS-1 (Requirement)
§25.963(a): Each fuel tank must be able to withstand, without failure, the vibration, inertia, fluid, and structural loads to which it may be subjected in operation.
- CFR Reference: 25.963
- Source: Derived from 14 CFR Part 25
- Criticality: Safety-Critical
- Verification Method: Test
- Compliance Status: Not Started

##### CERT-PWR-0202-DS-2 (Requirement)
§25.963(b): Flexible fuel tank liners must be approved or must be shown to be suitable for the particular application.
- CFR Reference: 25.963
- Source: Derived from 14 CFR Part 25
- Criticality: Safety-Critical
- Verification Method: Test
- Compliance Status: Not Started

##### CERT-PWR-0202-DS-3 (Requirement)
§25.963(d): Each fuel tank must be isolated from personnel compartments by fume-proof and fuel-proof enclosures.
- CFR Reference: 25.963
- Source: Derived from 14 CFR Part 25
- Criticality: Safety-Critical
- Verification Method: Test
- Compliance Status: Not Started

#### CERT-PWR-0203 (Requirement)
§25.981 Fuel Tank Explosion Prevention: Fuel tank flammability must be reduced by an acceptable Ignition Mitigation Means (IMM) or Flammability Reduction Means (FRM), or fuel tank must be located to minimize development of flammable vapors.
- CFR Reference: 25.981
- Source: 14 CFR Part 25
- Criticality: Safety-Critical
- Verification Method: Test
- Compliance Status: Not Started

##### CERT-PWR-0203-DS-1 (Requirement)
§25.981(a): No ignition source may be present at each point in the fuel tank or fuel tank system where catastrophic failure could occur due to ignition of fuel or vapors.
- CFR Reference: 25.981
- Source: Derived from 14 CFR Part 25
- Criticality: Safety-Critical
- Verification Method: Test
- Compliance Status: Not Started

##### CERT-PWR-0203-DS-2 (Requirement)
§25.981(b): Except as provided, no component whose failure could cause an ignition source may be installed in a fuel tank unless proven to not create a hazard under failure conditions.
- CFR Reference: 25.981
- Source: Derived from 14 CFR Part 25
- Criticality: Safety-Critical
- Verification Method: Test
- Compliance Status: Not Started

### Oil System
Oil System - 14 CFR 25.1011-25.1027
- CFR Reference: 25.1011-25.1027
- Source: 14 CFR Part 25

#### CERT-PWR-0301 (Requirement)
§25.1011 Oil System General: Each engine must have an independent oil system that can supply it with an appropriate quantity of oil at a temperature not above that safe for continuous operation.
- CFR Reference: 25.1011
- Source: 14 CFR Part 25
- Criticality: Safety-Critical
- Verification Method: Test
- Compliance Status: Not Started

##### CERT-PWR-0301-DS-1 (Requirement)
§25.1011(a): Each engine must have an independent oil system that can supply it with an appropriate quantity of oil at a temperature not above that safe for continuous operation.
- CFR Reference: 25.1011
- Source: Derived from 14 CFR Part 25
- Criticality: Safety-Critical
- Verification Method: Test
- Compliance Status: Not Started

##### CERT-PWR-0301-DS-2 (Requirement)
§25.1011(b): The usable oil tank capacity may not be less than the product of the endurance of the airplane under critical operating conditions and the maximum allowable oil consumption of the engine.
- CFR Reference: 25.1011
- Source: Derived from 14 CFR Part 25
- Criticality: Safety-Critical
- Verification Method: Test
- Compliance Status: Not Started

#### CERT-PWR-0302 (Requirement)
§25.1013 Oil Tanks: Each oil tank must be designed and installed to withstand applicable loads and have adequate structural strength. Oil tanks must allow proper draining and filling.
- CFR Reference: 25.1013
- Source: 14 CFR Part 25
- Criticality: Safety-Critical
- Verification Method: Test
- Compliance Status: Not Started

##### CERT-PWR-0302-DS-1 (Requirement)
§25.1013(a): Each oil tank must have an expansion space of not less than 10 percent of the tank capacity.
- CFR Reference: 25.1013
- Source: Derived from 14 CFR Part 25
- Criticality: Safety-Critical
- Verification Method: Test
- Compliance Status: Not Started

##### CERT-PWR-0302-DS-2 (Requirement)
§25.1013(b): Each oil tank must be vented from the top part of the expansion space.
- CFR Reference: 25.1013
- Source: Derived from 14 CFR Part 25
- Criticality: Safety-Critical
- Verification Method: Test
- Compliance Status: Not Started

##### CERT-PWR-0302-DS-3 (Requirement)
§25.1013(c): Each oil tank must provide an oil filler that is accessible, marked with contents, and has a closure that prevents loss of oil.
- CFR Reference: 25.1013
- Source: Derived from 14 CFR Part 25
- Criticality: Safety-Critical
- Verification Method: Test
- Compliance Status: Not Started

### Cooling
Cooling - 14 CFR 25.1041-25.1045
- CFR Reference: 25.1041-25.1045
- Source: 14 CFR Part 25

#### CERT-PWR-0401 (Requirement)
§25.1041 Cooling General: The powerplant and auxiliary power unit cooling provisions must be able to maintain the temperatures of powerplant components, engine fluids, and auxiliary power unit components and fluids within the temperature limits established for these components and fluids.
- CFR Reference: 25.1041
- Source: 14 CFR Part 25
- Criticality: Safety-Critical
- Verification Method: Test
- Compliance Status: Not Started

##### CERT-PWR-0401-DS-1 (Requirement)
§25.1041: Powerplant cooling provisions must maintain temperatures of powerplant components and fluids within established limits under ground, water, and flight operating conditions.
- CFR Reference: 25.1041
- Source: Derived from 14 CFR Part 25
- Criticality: Safety-Critical
- Verification Method: Test
- Compliance Status: Not Started

##### CERT-PWR-0401-DS-2 (Requirement)
§25.1041: Cooling must be maintained after normal engine or auxiliary power unit shutdown.
- CFR Reference: 25.1041
- Source: Derived from 14 CFR Part 25
- Criticality: Safety-Critical
- Verification Method: Test
- Compliance Status: Not Started

#### CERT-PWR-0402 (Requirement)
§25.1043 Cooling Tests: Cooling tests must be conducted to show compliance with cooling requirements. Compliance must be shown by flight test or analysis.
- CFR Reference: 25.1043
- Source: 14 CFR Part 25
- Criticality: Safety-Critical
- Verification Method: Test
- Compliance Status: Not Started

##### CERT-PWR-0402-DS-1 (Requirement)
§25.1043(a): Cooling tests must be conducted with the airplane in the configuration that is critical for cooling.
- CFR Reference: 25.1043
- Source: Derived from 14 CFR Part 25
- Criticality: Safety-Critical
- Verification Method: Test
- Compliance Status: Not Started

##### CERT-PWR-0402-DS-2 (Requirement)
§25.1043(b): Maximum ambient atmospheric temperature at which compliance has been established must be determined.
- CFR Reference: 25.1043
- Source: Derived from 14 CFR Part 25
- Criticality: Safety-Critical
- Verification Method: Test
- Compliance Status: Not Started

### Induction System
Induction System - 14 CFR 25.1091-25.1107
- CFR Reference: 25.1091-25.1107
- Source: 14 CFR Part 25

#### CERT-PWR-0501 (Requirement)
§25.1091 Air Induction: The air induction system for each engine and auxiliary power unit must supply the air required by that engine and auxiliary power unit under each operating condition for which certification is requested.
- CFR Reference: 25.1091
- Source: 14 CFR Part 25
- Criticality: Safety-Critical
- Verification Method: Test
- Compliance Status: Not Started

##### CERT-PWR-0501-DS-1 (Requirement)
§25.1091(a): The air induction system must supply the air required by each engine under each operating condition for which certification is requested.
- CFR Reference: 25.1091
- Source: Derived from 14 CFR Part 25
- Criticality: Safety-Critical
- Verification Method: Test
- Compliance Status: Not Started

##### CERT-PWR-0501-DS-2 (Requirement)
§25.1091(b): Each reciprocating engine must have an alternate air source that prevents the entry of rain, ice, or any other foreign matter.
- CFR Reference: 25.1091
- Source: Derived from 14 CFR Part 25
- Criticality: Safety-Critical
- Verification Method: Test
- Compliance Status: Not Started

##### CERT-PWR-0501-DS-3 (Requirement)
§25.1091(d): For turbine engine powered airplanes, there must be means to prevent hazardous quantities of fuel leakage from entering the engine intake system.
- CFR Reference: 25.1091
- Source: Derived from 14 CFR Part 25
- Criticality: Safety-Critical
- Verification Method: Test
- Compliance Status: Not Started

#### CERT-PWR-0502 (Requirement)
§25.1093 Induction System Icing Protection: Each reciprocating engine air induction system must have means to prevent and eliminate icing. Turbine engines must operate throughout their flight power range in icing conditions without adverse effects.
- CFR Reference: 25.1093
- Source: 14 CFR Part 25
- Criticality: Safety-Critical
- Verification Method: Test
- Compliance Status: Not Started

##### CERT-PWR-0502-DS-1 (Requirement)
§25.1093(a): Each reciprocating engine air induction system must have means to prevent and eliminate icing with adequate preheater capacity.
- CFR Reference: 25.1093
- Source: Derived from 14 CFR Part 25
- Criticality: Safety-Critical
- Verification Method: Test
- Compliance Status: Not Started

##### CERT-PWR-0502-DS-2 (Requirement)
§25.1093(b): Turbine engines with icing protection must operate throughout their flight power range in specified icing conditions without ice accumulation causing adverse engine operation.
- CFR Reference: 25.1093
- Source: Derived from 14 CFR Part 25
- Criticality: Safety-Critical
- Verification Method: Test
- Compliance Status: Not Started

##### CERT-PWR-0502-DS-3 (Requirement)
§25.1093(b)(2): Turbine engines must operate at ground idle for 30 minutes minimum on a concrete surface under specified icing conditions.
- CFR Reference: 25.1093
- Source: Derived from 14 CFR Part 25
- Criticality: Safety-Critical
- Verification Method: Test
- Compliance Status: Not Started

### Exhaust System
Exhaust System - 14 CFR 25.1121-25.1127
- CFR Reference: 25.1121-25.1127
- Source: 14 CFR Part 25

#### CERT-PWR-0601 (Requirement)
§25.1121 Exhaust System General: Each exhaust system must ensure safe disposal of exhaust gases without fire hazard or carbon monoxide contamination in any personnel compartment.
- CFR Reference: 25.1121
- Source: 14 CFR Part 25
- Criticality: Safety-Critical
- Verification Method: Test
- Compliance Status: Not Started

##### CERT-PWR-0601-DS-1 (Requirement)
§25.1121(a): Each exhaust system must ensure safe disposal of exhaust gases without fire hazard or carbon monoxide contamination in any personnel compartment.
- CFR Reference: 25.1121
- Source: Derived from 14 CFR Part 25
- Criticality: Safety-Critical
- Verification Method: Test
- Compliance Status: Not Started

##### CERT-PWR-0601-DS-2 (Requirement)
§25.1121(b): Each exhaust system part with surface hot enough to ignite flammable fluids must be located or shielded to prevent fires from leakage.
- CFR Reference: 25.1121
- Source: Derived from 14 CFR Part 25
- Criticality: Safety-Critical
- Verification Method: Test
- Compliance Status: Not Started

##### CERT-PWR-0601-DS-3 (Requirement)
§25.1121(e): No exhaust gases may discharge so as to cause a glare seriously affecting pilot vision at night.
- CFR Reference: 25.1121
- Source: Derived from 14 CFR Part 25
- Criticality: Safety-Critical
- Verification Method: Test
- Compliance Status: Not Started

#### CERT-PWR-0602 (Requirement)
§25.1123 Exhaust Piping: Exhaust piping must be supported and designed to withstand vibration, inertia, and other loads. Exhaust pipes must be separated from other components to prevent damage.
- CFR Reference: 25.1123
- Source: 14 CFR Part 25
- Criticality: Safety-Critical
- Verification Method: Test
- Compliance Status: Not Started

##### CERT-PWR-0602-DS-1 (Requirement)
§25.1123(a): Exhaust piping must be heat and corrosion resistant and must have provisions to prevent failure due to expansion.
- CFR Reference: 25.1123
- Source: Derived from 14 CFR Part 25
- Criticality: Safety-Critical
- Verification Method: Test
- Compliance Status: Not Started

##### CERT-PWR-0602-DS-2 (Requirement)
§25.1123(b): Exhaust piping connected to components between which relative motion could exist must have means for flexibility.
- CFR Reference: 25.1123
- Source: Derived from 14 CFR Part 25
- Criticality: Safety-Critical
- Verification Method: Test
- Compliance Status: Not Started

### Powerplant Controls and Accessories
Powerplant Controls and Accessories - 14 CFR 25.1141-25.1167
- CFR Reference: 25.1141-25.1167
- Source: 14 CFR Part 25

#### CERT-PWR-0701 (Requirement)
§25.1141 Powerplant Controls: General: Each powerplant control must be located, arranged, and designed under §§25.777 through 25.781 and marked under §25.1555. Controls must not be in locations where they might be inadvertently operated.
- CFR Reference: 25.1141
- Source: 14 CFR Part 25
- Criticality: Safety-Critical
- Verification Method: Test
- Compliance Status: Not Started

##### CERT-PWR-0701-DS-1 (Requirement)
§25.1141(a): Powerplant controls must not be located where persons entering, leaving, or moving normally in the cockpit might inadvertently operate them.
- CFR Reference: 25.1141
- Source: Derived from 14 CFR Part 25
- Criticality: Safety-Critical
- Verification Method: Test
- Compliance Status: Not Started

##### CERT-PWR-0701-DS-2 (Requirement)
§25.1141(b): Each flexible control must be approved or must be shown to be suitable for the particular application.
- CFR Reference: 25.1141
- Source: Derived from 14 CFR Part 25
- Criticality: Safety-Critical
- Verification Method: Test
- Compliance Status: Not Started

##### CERT-PWR-0701-DS-3 (Requirement)
§25.1141(d): Each control must be able to maintain any set position without constant attention by flight crewmembers and without creep due to control loads or vibration.
- CFR Reference: 25.1141
- Source: Derived from 14 CFR Part 25
- Criticality: Safety-Critical
- Verification Method: Test
- Compliance Status: Not Started

#### CERT-PWR-0702 (Requirement)
§25.1143 Engine Controls: There must be a separate power or thrust control for each engine. Power and thrust controls must provide individual and combined operation of all engines.
- CFR Reference: 25.1143
- Source: 14 CFR Part 25
- Criticality: Safety-Critical
- Verification Method: Test
- Compliance Status: Not Started

##### CERT-PWR-0702-DS-1 (Requirement)
§25.1143(a): There must be a separate power or thrust control for each engine.
- CFR Reference: 25.1143
- Source: Derived from 14 CFR Part 25
- Criticality: Safety-Critical
- Verification Method: Test
- Compliance Status: Not Started

##### CERT-PWR-0702-DS-2 (Requirement)
§25.1143(c): Each power and thrust control must provide a positive and immediately responsive means of controlling its engine.
- CFR Reference: 25.1143
- Source: Derived from 14 CFR Part 25
- Criticality: Safety-Critical
- Verification Method: Test
- Compliance Status: Not Started

##### CERT-PWR-0702-DS-3 (Requirement)
§25.1143(e): If a power or thrust control incorporates a fuel shutoff feature, it must have a means to prevent inadvertent movement to the shutoff position.
- CFR Reference: 25.1143
- Source: Derived from 14 CFR Part 25
- Criticality: Safety-Critical
- Verification Method: Test
- Compliance Status: Not Started

#### CERT-PWR-0703 (Requirement)
§25.1163 Powerplant Accessories: Each engine mounted accessory must be approved for mounting on the engine involved, use the provisions on the engine for mounting, and be sealed to prevent contamination.
- CFR Reference: 25.1163
- Source: 14 CFR Part 25
- Criticality: Safety-Critical
- Verification Method: Test
- Compliance Status: Not Started

##### CERT-PWR-0703-DS-1 (Requirement)
§25.1163(a): Each engine mounted accessory must be approved for mounting on the engine involved and use the provisions on the engine for mounting.
- CFR Reference: 25.1163
- Source: Derived from 14 CFR Part 25
- Criticality: Safety-Critical
- Verification Method: Test
- Compliance Status: Not Started

##### CERT-PWR-0703-DS-2 (Requirement)
§25.1163(b): Electrical equipment subject to arcing or sparking must be installed to minimize the probability of contact with any flammable fluids or vapors.
- CFR Reference: 25.1163
- Source: Derived from 14 CFR Part 25
- Criticality: Safety-Critical
- Verification Method: Test
- Compliance Status: Not Started

##### CERT-PWR-0703-DS-3 (Requirement)
§25.1163(c): If continued rotation of any engine-driven accessory is hazardous if malfunctioning occurs, there must be means to prevent rotation without interfering with engine operation.
- CFR Reference: 25.1163
- Source: Derived from 14 CFR Part 25
- Criticality: Safety-Critical
- Verification Method: Test
- Compliance Status: Not Started

### Powerplant Fire Protection
Powerplant Fire Protection - 14 CFR 25.1181-25.1207
- CFR Reference: 25.1181-25.1207
- Source: 14 CFR Part 25

#### CERT-PWR-0801 (Requirement)
§25.1181 Designated Fire Zones: Designated fire zones include the engine power section, engine accessory section, any complete powerplant compartment, any auxiliary power unit compartment, and combustion equipment installations.
- CFR Reference: 25.1181
- Source: 14 CFR Part 25
- Criticality: Safety-Critical
- Verification Method: Test
- Compliance Status: Not Started

##### CERT-PWR-0801-DS-1 (Requirement)
§25.1181(a)(1): The engine power section is a designated fire zone.
- CFR Reference: 25.1181
- Source: Derived from 14 CFR Part 25
- Criticality: Safety-Critical
- Verification Method: Test
- Compliance Status: Not Started

##### CERT-PWR-0801-DS-2 (Requirement)
§25.1181(a)(4): Any auxiliary power unit compartment is a designated fire zone.
- CFR Reference: 25.1181
- Source: Derived from 14 CFR Part 25
- Criticality: Safety-Critical
- Verification Method: Test
- Compliance Status: Not Started

##### CERT-PWR-0801-DS-3 (Requirement)
§25.1181(b): Each designated fire zone must meet the requirements of §§25.863, 25.865, 25.867, 25.869, and 25.1185 through 25.1203.
- CFR Reference: 25.1181
- Source: Derived from 14 CFR Part 25
- Criticality: Safety-Critical
- Verification Method: Test
- Compliance Status: Not Started

#### CERT-PWR-0802 (Requirement)
§25.1183 Flammable Fluid-Carrying Components: Lines, fittings, and components carrying flammable fluids in designated fire zones must be fire resistant. Flammable fluid tanks and supports must be fireproof or enclosed by fireproof shielding.
- CFR Reference: 25.1183
- Source: 14 CFR Part 25
- Criticality: Safety-Critical
- Verification Method: Test
- Compliance Status: Not Started

##### CERT-PWR-0802-DS-1 (Requirement)
§25.1183(a): Lines, fittings, and components carrying flammable fluids in designated fire zones must be at least fire resistant.
- CFR Reference: 25.1183
- Source: Derived from 14 CFR Part 25
- Criticality: Safety-Critical
- Verification Method: Test
- Compliance Status: Not Started

##### CERT-PWR-0802-DS-2 (Requirement)
§25.1183(a): Flammable fluid tanks and supports in designated fire zones must be fireproof or enclosed by a fireproof shield.
- CFR Reference: 25.1183
- Source: Derived from 14 CFR Part 25
- Criticality: Safety-Critical
- Verification Method: Test
- Compliance Status: Not Started

##### CERT-PWR-0802-DS-3 (Requirement)
§25.1183(c): All components in designated fire zones must be fireproof if their exposure to fire could cause fire spreading to other airplane regions.
- CFR Reference: 25.1183
- Source: Derived from 14 CFR Part 25
- Criticality: Safety-Critical
- Verification Method: Test
- Compliance Status: Not Started

#### CERT-PWR-0803 (Requirement)
§25.1191 Firewalls: Each engine, auxiliary power unit, fuel-burning heater, and combustion equipment must be isolated from the rest of the airplane by firewalls, shrouds, or equivalent means.
- CFR Reference: 25.1191
- Source: 14 CFR Part 25
- Criticality: Safety-Critical
- Verification Method: Test
- Compliance Status: Not Started

##### CERT-PWR-0803-DS-1 (Requirement)
§25.1191(a): Each engine and auxiliary power unit must be isolated from the rest of the airplane by firewalls, shrouds, or equivalent means.
- CFR Reference: 25.1191
- Source: Derived from 14 CFR Part 25
- Criticality: Safety-Critical
- Verification Method: Test
- Compliance Status: Not Started

##### CERT-PWR-0803-DS-2 (Requirement)
§25.1191(b)(1): Each firewall and shroud must be fireproof.
- CFR Reference: 25.1191
- Source: Derived from 14 CFR Part 25
- Criticality: Safety-Critical
- Verification Method: Test
- Compliance Status: Not Started

##### CERT-PWR-0803-DS-3 (Requirement)
§25.1191(b)(2): Each firewall must be constructed so that no hazardous quantity of air, fluid, or flame can pass from the compartment to other parts of the airplane.
- CFR Reference: 25.1191
- Source: Derived from 14 CFR Part 25
- Criticality: Safety-Critical
- Verification Method: Test
- Compliance Status: Not Started

#### CERT-PWR-0804 (Requirement)
§25.1195 Fire Extinguishing Systems: Each designated fire zone must have a fire extinguisher system, except for certain turbine engine sections. Agent quantity, discharge rate, and distribution must adequately extinguish fires.
- CFR Reference: 25.1195
- Source: 14 CFR Part 25
- Criticality: Safety-Critical
- Verification Method: Test
- Compliance Status: Not Started

##### CERT-PWR-0804-DS-1 (Requirement)
§25.1195(a): Except for combustor, turbine, and tail pipe sections of turbine engines, each designated fire zone must have a fire extinguisher system.
- CFR Reference: 25.1195
- Source: Derived from 14 CFR Part 25
- Criticality: Safety-Critical
- Verification Method: Test
- Compliance Status: Not Started

##### CERT-PWR-0804-DS-2 (Requirement)
§25.1195(b): The fire extinguishing system, agent quantity, rate of discharge, and distribution must be adequate to extinguish fires.
- CFR Reference: 25.1195
- Source: Derived from 14 CFR Part 25
- Criticality: Safety-Critical
- Verification Method: Test
- Compliance Status: Not Started

##### CERT-PWR-0804-DS-3 (Requirement)
§25.1195(b): Other than for APUs and heaters, each fire zone must have two discharges producing adequate agent concentration.
- CFR Reference: 25.1195
- Source: Derived from 14 CFR Part 25
- Criticality: Safety-Critical
- Verification Method: Test
- Compliance Status: Not Started

#### CERT-PWR-0805 (Requirement)
§25.1197 Fire Extinguishing Agents: Fire extinguishing agents must be capable of extinguishing flames from burning fluids in the protected area and have thermal stability over the temperature range experienced in storage compartments.
- CFR Reference: 25.1197
- Source: 14 CFR Part 25
- Criticality: Safety-Critical
- Verification Method: Test
- Compliance Status: Not Started

##### CERT-PWR-0805-DS-1 (Requirement)
§25.1197(a): Fire extinguishing agents must be capable of extinguishing flames emanating from any burning of fluids or combustible materials in the area protected.
- CFR Reference: 25.1197
- Source: Derived from 14 CFR Part 25
- Criticality: Safety-Critical
- Verification Method: Test
- Compliance Status: Not Started

##### CERT-PWR-0805-DS-2 (Requirement)
§25.1197(a): Fire extinguishing agents must have thermal stability over the temperature range likely to be experienced in the storage compartment.
- CFR Reference: 25.1197
- Source: Derived from 14 CFR Part 25
- Criticality: Safety-Critical
- Verification Method: Test
- Compliance Status: Not Started

##### CERT-PWR-0805-DS-3 (Requirement)
§25.1197(b): If toxic extinguishing agents are used, there must be means to prevent harmful concentrations from entering personnel compartments.
- CFR Reference: 25.1197
- Source: Derived from 14 CFR Part 25
- Criticality: Safety-Critical
- Verification Method: Test
- Compliance Status: Not Started

#### CERT-PWR-0806 (Requirement)
§25.1203 Fire Detector System: Fire or overheat detectors must be installed in designated fire zones and turbine engine compartment sections to ensure prompt detection of fire.
- CFR Reference: 25.1203
- Source: 14 CFR Part 25
- Criticality: Safety-Critical
- Verification Method: Test
- Compliance Status: Not Started

##### CERT-PWR-0806-DS-1 (Requirement)
§25.1203(a): Fire or overheat detectors must be provided for each designated fire zone and installed to ensure prompt detection of fire.
- CFR Reference: 25.1203
- Source: Derived from 14 CFR Part 25
- Criticality: Safety-Critical
- Verification Method: Test
- Compliance Status: Not Started

##### CERT-PWR-0806-DS-2 (Requirement)
§25.1203(b): Each fire detector system must warn the crew if a sensor or wiring is severed at any point, unless system continues to function.
- CFR Reference: 25.1203
- Source: Derived from 14 CFR Part 25
- Criticality: Safety-Critical
- Verification Method: Test
- Compliance Status: Not Started

##### CERT-PWR-0806-DS-3 (Requirement)
§25.1203(c): No fire or overheat detector may be affected by any oil, water, other fluids or fumes that might be present.
- CFR Reference: 25.1203
- Source: Derived from 14 CFR Part 25
- Criticality: Safety-Critical
- Verification Method: Test
- Compliance Status: Not Started

##### CERT-PWR-0806-DS-4 (Requirement)
§25.1203(e): Components of each fire detector system in a fire zone must be fire-resistant.
- CFR Reference: 25.1203
- Source: Derived from 14 CFR Part 25
- Criticality: Safety-Critical
- Verification Method: Test
- Compliance Status: Not Started

## SUBPART_F: Subpart F - Equipment (25.1301 - 25.1461) (Subpart)

### CERT-EQP-001 (Requirement)
Equipment Systems and Installations (25.1309): Equipment and systems must be designed to ensure they perform their intended functions under foreseeable operating conditions. Failure analysis required: Catastrophic failures must be extremely improbable (10^-9/FH), Hazardous extremely remote (10^-7/FH), Major remote (10^-5/FH).
- CFR Reference: 25.1301-25.1309
- Source: 14 CFR Part 25
- Criticality: Safety-Critical
- Verification Method: Analysis
- Compliance Status: Not Started

#### CERT-EQP-001-DS-1 (Requirement)
§25.1301(a): Each item of installed equipment must be of a kind and design appropriate to its intended function.
- CFR Reference: 25.1301-25.1309
- Source: Derived from 14 CFR Part 25
- Criticality: Safety-Critical
- Verification Method: Test
- Compliance Status: Not Started

#### CERT-EQP-001-DS-2 (Requirement)
§25.1301(b): Each item of installed equipment must be labeled as to its identification, function, or operating limitations.
- CFR Reference: 25.1301-25.1309
- Source: Derived from 14 CFR Part 25
- Criticality: Safety-Critical
- Verification Method: Test
- Compliance Status: Not Started

#### CERT-EQP-001-DS-3 (Requirement)
§25.1301(c): Each item of installed equipment must be installed according to limitations specified for that equipment.
- CFR Reference: 25.1301-25.1309
- Source: Derived from 14 CFR Part 25
- Criticality: Safety-Critical
- Verification Method: Test
- Compliance Status: Not Started

### CERT-EQP-002 (Requirement)
HIRF Protection: Electrical and electronic systems that perform functions whose failure would contribute to or cause catastrophic or hazardous failure conditions must be designed and installed to ensure operation in the High Intensity Radiated Fields (HIRF) environment.
- CFR Reference: 25.1316
- Source: 14 CFR Part 25
- Criticality: Safety-Critical
- Verification Method: Analysis
- Compliance Status: Not Started

#### CERT-EQP-002-DS-1 (Requirement)
§25.1303: Each required flight instrument must be visible from the appropriate pilots station, have adequate lighting, and have marking as prescribed.
- CFR Reference: 25.1316
- Source: Derived from 14 CFR Part 25
- Criticality: Safety-Critical
- Verification Method: Test
- Compliance Status: Not Started

#### CERT-EQP-002-DS-2 (Requirement)
§25.1305: Required powerplant instruments include fuel quantity, oil quantity, oil pressure, oil temperature, and engine tachometer for each engine.
- CFR Reference: 25.1316
- Source: Derived from 14 CFR Part 25
- Criticality: Safety-Critical
- Verification Method: Test
- Compliance Status: Not Started

#### CERT-EQP-002-DS-3 (Requirement)
§25.1321: Instrument arrangement and visibility must allow the flight crew to monitor the flight path and detect any failure or improper functioning of equipment.
- CFR Reference: 25.1316
- Source: Derived from 14 CFR Part 25
- Criticality: Safety-Critical
- Verification Method: Test
- Compliance Status: Not Started

### CERT-EQP-003 (Requirement)
Flight Crew Alerting: Warning, caution, and advisory alerts must be provided to the flightcrew. Must be prioritized appropriately and designed to minimize flightcrew errors. Red = Warning (immediate action), Amber = Caution (awareness/action), Blue/Green/White = Advisory.
- CFR Reference: 25.1322
- Source: 14 CFR Part 25
- Criticality: Safety-Critical
- Verification Method: Analysis
- Compliance Status: Not Started

#### CERT-EQP-003-DS-1 (Requirement)
§25.1351(a): Each electrical system must be adequate for the intended use and be designed so that the required load can be powered under any probable operating condition.
- CFR Reference: 25.1322
- Source: Derived from 14 CFR Part 25
- Criticality: Safety-Critical
- Verification Method: Test
- Compliance Status: Not Started

#### CERT-EQP-003-DS-2 (Requirement)
§25.1351(b): Generating system - each generating system must be designed so that no failure or malfunction of any one generating system can result in the loss of more than one source of electrical power.
- CFR Reference: 25.1322
- Source: Derived from 14 CFR Part 25
- Criticality: Safety-Critical
- Verification Method: Test
- Compliance Status: Not Started

#### CERT-EQP-003-DS-3 (Requirement)
§25.1351(d): Each system must be designed so that essential loads can be powered for a time period sufficient to complete an emergency landing under any probable operating condition.
- CFR Reference: 25.1322
- Source: Derived from 14 CFR Part 25
- Criticality: Safety-Critical
- Verification Method: Test
- Compliance Status: Not Started

### CERT-EQP-004 (Requirement)
Electrical Systems: The generating system must supply power for all required electrical equipment with adequate capacity and regulation. Bus architecture, emergency power (RAT/batteries), and electrical load analysis required.
- CFR Reference: 25.1351-25.1365
- Source: 14 CFR Part 25
- Criticality: Safety-Critical
- Verification Method: Analysis
- Compliance Status: Not Started

#### CERT-EQP-004-DS-1 (Requirement)
§25.1435(a): Each element of the hydraulic system must be designed and installed to function properly when installed, and each such element must be substantiated by proof pressure tests.
- CFR Reference: 25.1351-25.1365
- Source: Derived from 14 CFR Part 25
- Criticality: Safety-Critical
- Verification Method: Test
- Compliance Status: Not Started

#### CERT-EQP-004-DS-2 (Requirement)
§25.1435(b): The hydraulic system must be designed to perform the intended function under all foreseeable operating conditions with a means to ensure adequate fluid cleanliness.
- CFR Reference: 25.1351-25.1365
- Source: Derived from 14 CFR Part 25
- Criticality: Safety-Critical
- Verification Method: Test
- Compliance Status: Not Started

#### CERT-EQP-004-DS-3 (Requirement)
§25.1435(c): Hydraulic system fire protection must be provided to minimize hazards to the airplane from hydraulic fluid fires.
- CFR Reference: 25.1351-25.1365
- Source: Derived from 14 CFR Part 25
- Criticality: Safety-Critical
- Verification Method: Test
- Compliance Status: Not Started

## SUBPART_G: Subpart G - Operating Limitations and Information (25.1501 - 25.1587) (Subpart)

### CERT-OPS-001 (Requirement)
Operating Limitations: Airspeed limitations (V_MO/M_MO, V_A, V_FE, V_LE, V_LO), weight and CG limits, altitude limits, ambient temperature limits, and powerplant limitations must be established and documented in the AFM.
- CFR Reference: 25.1501-25.1533
- Source: 14 CFR Part 25
- Criticality: Regulatory
- Verification Method: Analysis
- Compliance Status: Not Started

#### CERT-OPS-001-DS-1 (Requirement)
§25.1501(a): Each operating limitation specified in §§25.1503 through 25.1533 and other limitations and information necessary for safe operation must be established.
- CFR Reference: 25.1501-25.1533
- Source: Derived from 14 CFR Part 25
- Criticality: Regulatory
- Verification Method: Demonstration
- Compliance Status: Not Started

#### CERT-OPS-001-DS-2 (Requirement)
§25.1501(b): The operating limitations and other information necessary for safe operation must be made available to the crewmembers as prescribed.
- CFR Reference: 25.1501-25.1533
- Source: Derived from 14 CFR Part 25
- Criticality: Regulatory
- Verification Method: Demonstration
- Compliance Status: Not Started

#### CERT-OPS-001-DS-3 (Requirement)
§25.1503: Airspeed limitations - VMO/MMO, VD/MD, and the speed for maximum gust intensity must be established so that they provide adequate margin for probable variations in pilot technique and atmospheric conditions.
- CFR Reference: 25.1501-25.1533
- Source: Derived from 14 CFR Part 25
- Criticality: Regulatory
- Verification Method: Demonstration
- Compliance Status: Not Started

### CERT-OPS-002 (Requirement)
Airplane Flight Manual (AFM): An AFM must be provided containing: operating limitations, procedures (normal, abnormal, emergency), performance data, and weight/balance information. Must be approved by the FAA and must be available in the airplane.
- CFR Reference: 25.1581-25.1587
- Source: 14 CFR Part 25
- Criticality: Regulatory
- Verification Method: Analysis
- Compliance Status: Not Started

#### CERT-OPS-002-DS-1 (Requirement)
§25.1581: An Airplane Flight Manual (AFM) must be furnished with each airplane and contain the information required by §§25.1583 through 25.1587.
- CFR Reference: 25.1581-25.1587
- Source: Derived from 14 CFR Part 25
- Criticality: Regulatory
- Verification Method: Demonstration
- Compliance Status: Not Started

#### CERT-OPS-002-DS-2 (Requirement)
§25.1583: The AFM operating limitations section must include VMO/MMO, takeoff and landing weights and CG limits, and kinds of operation authorized.
- CFR Reference: 25.1581-25.1587
- Source: Derived from 14 CFR Part 25
- Criticality: Regulatory
- Verification Method: Demonstration
- Compliance Status: Not Started

#### CERT-OPS-002-DS-3 (Requirement)
§25.1585: The AFM operating procedures section must include normal, abnormal, and emergency procedures, including procedures for making a balked landing and for ditching if applicable.
- CFR Reference: 25.1581-25.1587
- Source: Derived from 14 CFR Part 25
- Criticality: Regulatory
- Verification Method: Demonstration
- Compliance Status: Not Started

## SUBPART_H: Subpart H - Electrical Wiring Interconnection Systems (25.1701 - 25.1733) (Subpart)

### CERT-EWIS-001 (Requirement)
EWIS Requirements: EWIS must be designed and installed to minimize fire hazards and electromagnetic interference. Separation requirements from fuel, hydraulic, and oxygen systems. Wire sizing, protection, and identification requirements. EWIS Instructions for Continued Airworthiness required.
- CFR Reference: 25.1701-25.1733
- Source: 14 CFR Part 25
- Criticality: Safety-Critical
- Verification Method: Analysis
- Compliance Status: Not Started

#### CERT-EWIS-001-DS-1 (Requirement)
The applicant shall decompose 14 CFR §25.1701-25.1733 into lower-level system, subsystem, and operational requirements as applicable.
Bidirectional traceability shall be maintained from this derived set back to the parent requirement (CERT-EWIS-001).
- CFR Reference: 25.1701-25.1733
- Source: Derived from 14 CFR Part 25
- Criticality: Safety-Critical
- Verification Method: Analysis
- Compliance Status: Not Started

#### CERT-EWIS-001-DS-2 (Requirement)
The applicant shall define the Means of Compliance (MoC) for 14 CFR §25.1701-25.1733 (e.g., analysis, test, inspection, similarity) and the acceptance criteria.
Compliance shall be verified and objective evidence shall be recorded and reviewed against the acceptance criteria.
- CFR Reference: 25.1701-25.1733
- Source: Derived from 14 CFR Part 25
- Criticality: Safety-Critical
- Verification Method: Analysis
- Compliance Status: Not Started

#### CERT-EWIS-001-DS-3 (Requirement)
The applicant shall maintain configuration-controlled compliance artifacts for 14 CFR §25.1701-25.1733, including assumptions, limitations, and supporting reports/data.
All evidence shall be linked to the approved configuration baseline and remain retrievable for audits and certification review.
- CFR Reference: 25.1701-25.1733
- Source: Derived from 14 CFR Part 25
- Criticality: Safety-Critical
- Verification Method: Analysis
- Compliance Status: Not Started

## SUBPART_APPENDIX: Appendices (A through O) (Subpart)

### CERT-APP-001 (Requirement)
Icing Conditions (Appendix C): Defines atmospheric icing conditions (continuous maximum and intermittent maximum) for certification. LWC, droplet diameter, temperature ranges. Basis for ice protection system design and testing.
- CFR Reference: Appendix C
- Source: 14 CFR Part 25
- Criticality: Safety-Critical
- Verification Method: Analysis
- Compliance Status: Not Started

#### CERT-APP-001-DS-1 (Requirement)
Appendix C Part I: Continuous maximum icing conditions are defined in terms of liquid water content, mean effective diameter of the cloud droplets, and ambient air temperature.
- CFR Reference: Appendix C
- Source: Derived from 14 CFR Part 25
- Criticality: Safety-Critical
- Verification Method: Analysis
- Compliance Status: Not Started

#### CERT-APP-001-DS-2 (Requirement)
Appendix C Part II: Intermittent maximum icing conditions (freezing rain) are defined by the freezing rain environment parameters.
- CFR Reference: Appendix C
- Source: Derived from 14 CFR Part 25
- Criticality: Safety-Critical
- Verification Method: Analysis
- Compliance Status: Not Started

#### CERT-APP-001-DS-3 (Requirement)
§25.1419: Ice protection must be designed and installed so that the airplane is capable of operating safely in continuous and intermittent maximum icing conditions as defined in Appendix C.
- CFR Reference: Appendix C
- Source: Derived from 14 CFR Part 25
- Criticality: Safety-Critical
- Verification Method: Analysis
- Compliance Status: Not Started

### CERT-APP-002 (Requirement)
Emergency Evacuation (Appendix J): Full-scale emergency evacuation demonstration required. All passengers and crew must evacuate within 90 seconds using half of the available exits. Night lighting conditions, realistic passenger demographics.
- CFR Reference: Appendix J
- Source: 14 CFR Part 25
- Criticality: Safety-Critical
- Verification Method: Analysis
- Compliance Status: Not Started

#### CERT-APP-002-DS-1 (Requirement)
Appendix O: Supercooled large drop (SLD) icing conditions are defined in terms of freezing drizzle and freezing rain parameters.
- CFR Reference: Appendix J
- Source: Derived from 14 CFR Part 25
- Criticality: Safety-Critical
- Verification Method: Analysis
- Compliance Status: Not Started

#### CERT-APP-002-DS-2 (Requirement)
§25.1420: If certification for flight in SLD icing conditions is sought, the applicant must demonstrate safe operation in Appendix O conditions.
- CFR Reference: Appendix J
- Source: Derived from 14 CFR Part 25
- Criticality: Safety-Critical
- Verification Method: Analysis
- Compliance Status: Not Started

#### CERT-APP-002-DS-3 (Requirement)
§25.1420(a): Means must be provided to detect SLD icing conditions and alert the flight crew when operating in those conditions.
- CFR Reference: Appendix J
- Source: Derived from 14 CFR Part 25
- Criticality: Safety-Critical
- Verification Method: Analysis
- Compliance Status: Not Started

### CERT-APP-003 (Requirement)
ETOPS (Appendix K): Extended Operations requirements for twin-engine airplanes. Diversion time up to 180+ minutes from adequate airport. Reliability, propulsion system monitoring, ETOPS maintenance program, and route-specific considerations.
- CFR Reference: Appendix K
- Source: 14 CFR Part 25
- Criticality: Safety-Critical
- Verification Method: Analysis
- Compliance Status: Not Started

#### CERT-APP-003-DS-1 (Requirement)
Appendix I: Takeoff and landing performance on wet and contaminated runways must be determined in accordance with this appendix.
- CFR Reference: Appendix K
- Source: Derived from 14 CFR Part 25
- Criticality: Safety-Critical
- Verification Method: Analysis
- Compliance Status: Not Started

#### CERT-APP-003-DS-2 (Requirement)
§25.109: Accelerate-stop distance on wet runways must account for reduced braking effectiveness.
- CFR Reference: Appendix K
- Source: Derived from 14 CFR Part 25
- Criticality: Safety-Critical
- Verification Method: Analysis
- Compliance Status: Not Started

#### CERT-APP-003-DS-3 (Requirement)
§25.125: Landing distance on wet runways is 115% of the landing distance on dry runways unless specific wet runway data is approved.
- CFR Reference: Appendix K
- Source: Derived from 14 CFR Part 25
- Criticality: Safety-Critical
- Verification Method: Analysis
- Compliance Status: Not Started

### CERT-APP-004 (Requirement)
Supercooled Large Droplets (Appendix O): Defines SLD icing conditions including freezing drizzle and freezing rain. Required for aircraft seeking certification for flight in SLD conditions. Extended droplet size distributions beyond Appendix C.
- CFR Reference: Appendix O
- Source: 14 CFR Part 25
- Criticality: Safety-Critical
- Verification Method: Analysis
- Compliance Status: Not Started

#### CERT-APP-004-DS-1 (Requirement)
Appendix D: Criteria for demonstration of the emergency evacuation procedures specified in §25.803 are established.
- CFR Reference: Appendix O
- Source: Derived from 14 CFR Part 25
- Criticality: Safety-Critical
- Verification Method: Analysis
- Compliance Status: Not Started

#### CERT-APP-004-DS-2 (Requirement)
§25.1529: Instructions for Continued Airworthiness (ICA) must be prepared and included in the maintenance manual or appropriate maintenance instructions.
- CFR Reference: Appendix O
- Source: Derived from 14 CFR Part 25
- Criticality: Safety-Critical
- Verification Method: Analysis
- Compliance Status: Not Started

#### CERT-APP-004-DS-3 (Requirement)
§25.1533: For airplanes with MMEL provisions, the operating limitations must include the limitations resulting from the MMEL, if any.
- CFR Reference: Appendix O
- Source: Derived from 14 CFR Part 25
- Criticality: Safety-Critical
- Verification Method: Analysis
- Compliance Status: Not Started

## CERT-GEN-002 (Requirement)
ETOPS Type Design Approval: For ETOPS (Extended Operations) beyond 60 minutes from an adequate airport, the applicant must demonstrate the airplane-engine combination is capable of safe flight considering catastrophic single failures and adverse operating conditions.
- CFR Reference: 25.3
- Source: 14 CFR Part 25
- Criticality: Safety-Critical
- Verification Method: Analysis
- Compliance Status: Not Started

## CAT_B_PERF: Performance Requirements (Category)

## CAT_B_CTRL: Controllability and Maneuverability (Category)

## CERT-FLT-005 (Requirement)
General Controllability: The airplane must be safely controllable and maneuverable during all flight phases including takeoff, climb, cruise, descent, approach, landing, and engine-out conditions. No exceptional piloting skill or strength shall be required.
- CFR Reference: 25.143
- Source: 14 CFR Part 25
- Criticality: Safety-Critical
- Verification Method: Analysis
- Compliance Status: Not Started

## CERT-FLT-006 (Requirement)
Directional and Lateral Control: The airplane must have adequate directional and lateral control with the critical engine inoperative. V_MC (minimum control speed) must be established and demonstrated.
- CFR Reference: 25.147
- Source: 14 CFR Part 25
- Criticality: Safety-Critical
- Verification Method: Analysis
- Compliance Status: Not Started

## CAT_B_STAB: Stability Requirements (Category)

## CERT-FLT-007 (Requirement)
Static Stability: The airplane must exhibit positive static longitudinal stability in all configurations. Stick force gradients must provide natural feel and proper speed stability characteristics.
- CFR Reference: 25.171-25.181
- Source: 14 CFR Part 25
- Criticality: Safety-Critical
- Verification Method: Analysis
- Compliance Status: Not Started

## CERT-FLT-008 (Requirement)
Stall Characteristics: The airplane must have adequate stall warning and stall characteristics. During stall entry and recovery, there shall be no uncontrollable pitching, rolling, or yawing. Stall warning must occur at least 5 knots before stall.
- CFR Reference: 25.201-25.207
- Source: 14 CFR Part 25
- Criticality: Safety-Critical
- Verification Method: Analysis
- Compliance Status: Not Started

## CAT_C_LOADS: Flight Loads (Category)

## CAT_C_FAT: Fatigue and Damage Tolerance (Category)

## CERT-STR-005 (Requirement)
Lightning Protection: The airplane must be protected against catastrophic effects of lightning. Direct and swept lightning attachment points, fuel system protection, and electromagnetic effects on electrical/electronic systems must be addressed.
- CFR Reference: 25.581
- Source: 14 CFR Part 25
- Criticality: Safety-Critical
- Verification Method: Analysis
- Compliance Status: Not Started

## CERT-DES-005 (Requirement)
Fire Protection: Fire zones must have approved fire detection and extinguishing systems. Cabin interior materials must meet flammability requirements (12-second vertical burn test, heat release, smoke density). Cargo compartment fire protection classification.
- CFR Reference: 25.851-25.869
- Source: 14 CFR Part 25
- Criticality: Safety-Critical
- Verification Method: Analysis
- Compliance Status: Not Started

## CERT-GEN-002-DS-1 (Requirement)
§25.3(a): The applicant must demonstrate that the airplane-engine combination is capable of safe extended operations beyond 60 minutes from an adequate airport.
- CFR Reference: 25.3
- Source: Derived from 14 CFR Part 25
- Criticality: Safety-Critical
- Verification Method: Analysis
- Compliance Status: Not Started

## CERT-GEN-002-DS-2 (Requirement)
§25.3(b): ETOPS eligibility requires demonstration of safe flight considering catastrophic single failures and adverse operating conditions.
- CFR Reference: 25.3
- Source: Derived from 14 CFR Part 25
- Criticality: Safety-Critical
- Verification Method: Analysis
- Compliance Status: Not Started

## CERT-GEN-002-DS-3 (Requirement)
§25.3(c): The applicant must identify ETOPS-critical systems and establish maintenance requirements for continued airworthiness.
- CFR Reference: 25.3
- Source: Derived from 14 CFR Part 25
- Criticality: Safety-Critical
- Verification Method: Analysis
- Compliance Status: Not Started

## CERT-FLT-005-DS-1 (Requirement)
§25.143(a): The airplane must be safely controllable and maneuverable during takeoff, climb, level flight, descent, and landing.
- CFR Reference: 25.143
- Source: Derived from 14 CFR Part 25
- Criticality: Safety-Critical
- Verification Method: Test
- Compliance Status: Not Started

## CERT-FLT-005-DS-2 (Requirement)
§25.143(b): It must be possible to make a smooth transition from one flight condition to any other flight condition without exceptional piloting skill, alertness, or strength.
- CFR Reference: 25.143
- Source: Derived from 14 CFR Part 25
- Criticality: Safety-Critical
- Verification Method: Test
- Compliance Status: Not Started

## CERT-FLT-005-DS-3 (Requirement)
§25.143(d): Control forces may not exceed: Pitch 75 lbs (short term), 10 lbs (long term); Roll 50 lbs (short term), 5 lbs (long term); Yaw 150 lbs (short term), 20 lbs (long term).
- CFR Reference: 25.143
- Source: Derived from 14 CFR Part 25
- Criticality: Safety-Critical
- Verification Method: Test
- Compliance Status: Not Started

## CERT-FLT-006-DS-1 (Requirement)
§25.147(a): For turbopropeller aircraft, takeoff must be possible using normal piloting skill when the critical engine suddenly becomes inoperative.
- CFR Reference: 25.147
- Source: Derived from 14 CFR Part 25
- Criticality: Safety-Critical
- Verification Method: Test
- Compliance Status: Not Started

## CERT-FLT-006-DS-2 (Requirement)
§25.147(c): For all airplanes, it must be possible to safely make a reasonably sudden change in heading of up to 15 degrees at 1.4VSR1.
- CFR Reference: 25.147
- Source: Derived from 14 CFR Part 25
- Criticality: Safety-Critical
- Verification Method: Test
- Compliance Status: Not Started

## CERT-FLT-006-DS-3 (Requirement)
§25.147(e): VMC is the calibrated airspeed at which, when the critical engine is suddenly made inoperative, it is possible to maintain control with a bank of not more than 5 degrees.
- CFR Reference: 25.147
- Source: Derived from 14 CFR Part 25
- Criticality: Safety-Critical
- Verification Method: Test
- Compliance Status: Not Started

## CERT-FLT-007-DS-1 (Requirement)
§25.171: The airplane must be longitudinally, directionally, and laterally stable in accordance with the provisions of §§25.173 through 25.181.
- CFR Reference: 25.171-25.181
- Source: Derived from 14 CFR Part 25
- Criticality: Safety-Critical
- Verification Method: Test
- Compliance Status: Not Started

## CERT-FLT-007-DS-2 (Requirement)
§25.173: Static longitudinal stability - the stick force curve must have a stable slope at speeds between 85% and 115% of the trim speed.
- CFR Reference: 25.171-25.181
- Source: Derived from 14 CFR Part 25
- Criticality: Safety-Critical
- Verification Method: Test
- Compliance Status: Not Started

## CERT-FLT-007-DS-3 (Requirement)
§25.181: Dynamic stability - any short-period oscillation must be heavily damped; any combined lateral-directional oscillations must be positively damped.
- CFR Reference: 25.171-25.181
- Source: Derived from 14 CFR Part 25
- Criticality: Safety-Critical
- Verification Method: Test
- Compliance Status: Not Started

## CERT-FLT-008-DS-1 (Requirement)
§25.201(a): Stall characteristics must be demonstrated in straight flight and in 30-degree banked turns with power off and at maximum continuous power.
- CFR Reference: 25.201-25.207
- Source: Derived from 14 CFR Part 25
- Criticality: Safety-Critical
- Verification Method: Test
- Compliance Status: Not Started

## CERT-FLT-008-DS-2 (Requirement)
§25.201(b): During the stall tests, it must be possible to prevent more than 15 degrees of roll or yaw by the normal use of the controls.
- CFR Reference: 25.201-25.207
- Source: Derived from 14 CFR Part 25
- Criticality: Safety-Critical
- Verification Method: Test
- Compliance Status: Not Started

## CERT-FLT-008-DS-3 (Requirement)
§25.201(c): The airplane must give a clear and distinctive stall warning with sufficient margin to prevent inadvertent stalling.
- CFR Reference: 25.201-25.207
- Source: Derived from 14 CFR Part 25
- Criticality: Safety-Critical
- Verification Method: Test
- Compliance Status: Not Started

## CERT-STR-005-DS-1 (Requirement)
§25.631(a): The empennage structure must be designed to assure capability of continued safe flight and landing after impact with a 4-pound bird at VC.
- CFR Reference: 25.581
- Source: Derived from 14 CFR Part 25
- Criticality: Safety-Critical
- Verification Method: Analysis/Test
- Compliance Status: Not Started

## CERT-STR-005-DS-2 (Requirement)
§25.631(b): The airplane must be capable of successfully completing the flight after impact with a 4-pound bird when damage locations are in accordance with the requirements.
- CFR Reference: 25.581
- Source: Derived from 14 CFR Part 25
- Criticality: Safety-Critical
- Verification Method: Analysis/Test
- Compliance Status: Not Started

## CERT-STR-005-DS-3 (Requirement)
§25.775: Windshields and windows must be made of material that will not break into dangerous fragments when subjected to a 4-pound bird impact at VC.
- CFR Reference: 25.581
- Source: Derived from 14 CFR Part 25
- Criticality: Safety-Critical
- Verification Method: Analysis/Test
- Compliance Status: Not Started

## CERT-DES-005-DS-1 (Requirement)
§25.853(a): Each compartment occupied by the crew or passengers must meet the flammability requirements of Appendix F or other approved equivalent.
- CFR Reference: 25.851-25.869
- Source: Derived from 14 CFR Part 25
- Criticality: Safety-Critical
- Verification Method: Inspection
- Compliance Status: Not Started

## CERT-DES-005-DS-2 (Requirement)
§25.853(d): Each compartment must have a means to allow smoke to be dissipated to prevent obscuration of visibility to the extent necessary for the flight crew to perform their duties.
- CFR Reference: 25.851-25.869
- Source: Derived from 14 CFR Part 25
- Criticality: Safety-Critical
- Verification Method: Inspection
- Compliance Status: Not Started

## CERT-DES-005-DS-3 (Requirement)
§25.855: Each cargo or baggage compartment must be classified according to means of detecting and suppressing fire.
- CFR Reference: 25.851-25.869
- Source: Derived from 14 CFR Part 25
- Criticality: Safety-Critical
- Verification Method: Inspection
- Compliance Status: Not Started
